-- This is not a manufacturer provided MIB file. It was created
-- to satisfy the needs of the SNMP Tango device for the Carel
-- rack controllers found in the low-ITF.

CAREL-RACK-CONTROLLER DEFINITIONS ::= BEGIN

IMPORTS
    MODULE-IDENTITY, OBJECT-TYPE, NOTIFICATION-TYPE,
    enterprises, Integer32, Opaque
        FROM SNMPv2-SMI;

carel OBJECT IDENTIFIER ::= {enterprises 9839}

rack OBJECT IDENTIFIER ::= {carel 1}
values OBJECT IDENTIFIER ::= {rack 2}

coldTopTemperature OBJECT-TYPE
    SYNTAX      Opaque
    MAX-ACCESS  read-only
    STATUS      current
    DESCRIPTION
            "The current reading from the cold-top temperature sensor."
    ::= {values 61}

coldBottomTemperature OBJECT-TYPE
    SYNTAX      Opaque
    MAX-ACCESS  read-only
    STATUS      current
    DESCRIPTION
            "The current reading from the cold-bottom temperature sensor."
    ::= {values 62}

warmTopTemperature OBJECT-TYPE
    SYNTAX      Opaque
    MAX-ACCESS  read-only
    STATUS      current
    DESCRIPTION
            "The current reading from the warm-top temperature sensor."
    ::= {values 63}

warmBottomTemperature OBJECT-TYPE
    SYNTAX      Opaque
    MAX-ACCESS  read-only
    STATUS      current
    DESCRIPTION
            "The current reading from the warm-bottom temperature sensor."
    ::= {values 64}

differentialPressure OBJECT-TYPE
    SYNTAX      Integer32
    MAX-ACCESS  read-only
    STATUS      current
    DESCRIPTION
            "The current reading from the differential pressure sensor."
    ::= {values 65}

fan1Speed OBJECT-TYPE
    SYNTAX      Integer32
    MAX-ACCESS  read-only
    STATUS      current
    DESCRIPTION
            "The current speed of fan 1 in RPM."
    ::= {values 66}

fan2Speed OBJECT-TYPE
    SYNTAX      Integer32
    MAX-ACCESS  read-only
    STATUS      current
    DESCRIPTION
            "The current speed of fan 2 in RPM."
    ::= {values 67}

waterSupplyTemperature OBJECT-TYPE
    SYNTAX      Opaque
    MAX-ACCESS  read-only
    STATUS      current
    DESCRIPTION
            "The current water supply temperature."
    ::= {values 68}

waterFlow OBJECT-TYPE
    SYNTAX      Opaque
    MAX-ACCESS  read-only
    STATUS      current
    DESCRIPTION
            "The current water flow in Litres/Minute."
    ::= {values 69}

waterValvePercentage OBJECT-TYPE
    SYNTAX      Opaque
    MAX-ACCESS  read-only
    STATUS      current
    DESCRIPTION
            "The current water valve setting."
    ::= {values 70}

fanPercentage OBJECT-TYPE
    SYNTAX      Opaque
    MAX-ACCESS  read-only
    STATUS      current
    DESCRIPTION
            "The current fan speed setting."
    ::= {values 71}

END
